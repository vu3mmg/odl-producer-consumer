module example-consumer {
    yang-version 1;
    namespace "urn:opendaylight:params:xml:ns:yang:example:consumer";
    prefix "example-consumer";

    import config { prefix config; revision-date 2013-04-05; }
    import opendaylight-md-sal-binding { prefix md-sal-binding; revision-date 2013-10-28;}

    description
        "Service definition for example project";

    revision "2014-12-10" {
        description
            "Initial revision";
    }

    identity example-consumer {
        base config:module-type;
        config:java-name-prefix ExampleConsumer;
    }

    augment "/config:modules/config:module/config:configuration" {
        case example-consumer {
            when "/config:modules/config:module/config:type = 'example-consumer'";
            container broker {
                uses config:service-ref {
                    refine type {
                        mandatory true;
                        config:required-identity md-sal-binding:binding-broker-osgi-registry;
                    }
                }
            }
        }
    }
}
